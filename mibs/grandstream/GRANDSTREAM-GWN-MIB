GRANDSTREAM-GWN-MIB DEFINITIONS ::= BEGIN
 
		IMPORTS
			enterprises, TimeTicks, IpAddress, Integer32, Counter32, 
			OBJECT-TYPE, MODULE-IDENTITY			
				FROM SNMPv2-SMI			
			DisplayString, MacAddress			
				FROM SNMPv2-TC;
	
	
		-- 1.3.6.1.4.1.42397.1.1
		gwnMIB MODULE-IDENTITY 
			LAST-UPDATED "Invalid DateTime"		-- Invalid DateTime
			ORGANIZATION 
				"Organization."
			CONTACT-INFO 
				"Contact-info."
			DESCRIPTION 
				"Description."
			::= { gwn 1 }

		
	
	
--
-- Node definitions
--
	
--   1.3.6.1.4.1.2019
-- August 19, 2019 at 17:01 GMT
-- 1.3.6.1.4.1.42397.1.1
-- August 21, 2019 at 10:00 GMT
-- 
-- Node definitions
-- 
-- 1.3.6.1.4.1.42397
		-- 1.3.6.1.4.1.42397
		grandstream OBJECT IDENTIFIER ::= { enterprises 42397 }

		
--  1.3.6.1.4.1.42397.1
		-- 1.3.6.1.4.1.42397.1
		gwn OBJECT IDENTIFIER ::= { grandstream 1 }

		
--  1.3.6.1.4.1.42397.1.1.1
		-- 1.3.6.1.4.1.42397.1.1.2
		gwnApSystemInfo OBJECT IDENTIFIER ::= { gwnMIB 2 }

		
		-- 1.3.6.1.4.1.42397.1.1.2.1
		gwnDeviceModel OBJECT-TYPE
			SYNTAX DisplayString
			MAX-ACCESS read-only
			STATUS current
			DESCRIPTION
				"Description."
			::= { gwnApSystemInfo 1 }

		
		-- 1.3.6.1.4.1.42397.1.1.2.2
		gwnDeviceName OBJECT-TYPE
			SYNTAX DisplayString
			MAX-ACCESS read-only
			STATUS current
			DESCRIPTION
				"Description."
			::= { gwnApSystemInfo 2 }

		
		-- 1.3.6.1.4.1.42397.1.1.2.3
		gwnDeviceMac OBJECT-TYPE
			SYNTAX MacAddress
			MAX-ACCESS read-only
			STATUS current
			DESCRIPTION
				"Description."
			::= { gwnApSystemInfo 3 }

		
		-- 1.3.6.1.4.1.42397.1.1.2.4
		gwnDeviceVersion OBJECT-TYPE
			SYNTAX DisplayString
			MAX-ACCESS read-only
			STATUS current
			DESCRIPTION
				"Description."
			::= { gwnApSystemInfo 4 }

		
		-- 1.3.6.1.4.1.42397.1.1.2.5
		gwnDeviceIPAddress OBJECT-TYPE
			SYNTAX IpAddress
			MAX-ACCESS read-only
			STATUS current
			DESCRIPTION
				"Description."
			::= { gwnApSystemInfo 5 }

		
		-- 1.3.6.1.4.1.42397.1.1.2.6
		gwnDeviceUptime OBJECT-TYPE
			SYNTAX Counter32
			MAX-ACCESS read-only
			STATUS current
			DESCRIPTION
				"Description."
			::= { gwnApSystemInfo 6 }

		
		-- 1.3.6.1.4.1.42397.1.1.3
		gwnApWireless OBJECT IDENTIFIER ::= { gwnMIB 3 }

		
		-- 1.3.6.1.4.1.42397.1.1.3.1
		gwnRadioTable OBJECT-TYPE
			SYNTAX SEQUENCE OF GwnRadioEntry
			MAX-ACCESS not-accessible
			STATUS current
			DESCRIPTION
				"Description."
			::= { gwnApWireless 1 }

		
		-- 1.3.6.1.4.1.42397.1.1.3.1.1
		gwnRadioEntry OBJECT-TYPE
			SYNTAX GwnRadioEntry
			MAX-ACCESS not-accessible
			STATUS current
			DESCRIPTION
				"Description."
			INDEX { gwnRadioIndex }
			::= { gwnRadioTable 1 }

		
		GwnRadioEntry ::=
			SEQUENCE { 
				gwnRadioIndex
					Integer32,
				gwnRadioName
					DisplayString,
				gwnRadioStatus
					INTEGER,
				gwnRadioChannel
					Integer32,
				gwnRadioTransmitPower
					Integer32,
				gwnRadioTxTotalFrames
					Counter32,
				gwnRadioTxMgmtFrames
					Counter32,
				gwnRadioTxDataFrames
					Counter32,
				gwnRadioTxDataBytes
					Counter32,
				gwnRadioTxDrops
					Counter32,
				gwnRadioRxTotalFrames
					Counter32,
				gwnRadioRxDataFrames
					Counter32,
				gwnRadioRxDataBytes
					Counter32,
				gwnRadioRxMgmtFrames
					Counter32,
				gwnRadioRxBad
					Counter32
			 }

		-- 1.3.6.1.4.1.42397.1.1.3.1.1.1
		gwnRadioIndex OBJECT-TYPE
			SYNTAX Integer32
			MAX-ACCESS read-only
			STATUS current
			DESCRIPTION
				"Description."
			::= { gwnRadioEntry 1 }

		
		-- 1.3.6.1.4.1.42397.1.1.3.1.1.2
		gwnRadioName OBJECT-TYPE
			SYNTAX DisplayString
			MAX-ACCESS read-only
			STATUS current
			DESCRIPTION
				"Description."
			::= { gwnRadioEntry 2 }

		
		-- 1.3.6.1.4.1.42397.1.1.3.1.1.3
		gwnRadioStatus OBJECT-TYPE
			SYNTAX INTEGER
			MAX-ACCESS read-only
			STATUS current
			DESCRIPTION
				"Description."
			::= { gwnRadioEntry 3 }

		
		-- 1.3.6.1.4.1.42397.1.1.3.1.1.4
		gwnRadioChannel OBJECT-TYPE
			SYNTAX Integer32
			MAX-ACCESS read-only
			STATUS current
			DESCRIPTION
				"Description."
			::= { gwnRadioEntry 4 }

		
		-- 1.3.6.1.4.1.42397.1.1.3.1.1.5
		gwnRadioTransmitPower OBJECT-TYPE
			SYNTAX Integer32
			MAX-ACCESS read-only
			STATUS current
			DESCRIPTION
				"Description."
			::= { gwnRadioEntry 5 }

		
		-- 1.3.6.1.4.1.42397.1.1.3.1.1.6
		gwnRadioTxTotalFrames OBJECT-TYPE
			SYNTAX Counter32
			MAX-ACCESS read-only
			STATUS current
			DESCRIPTION
				"Description."
			::= { gwnRadioEntry 6 }

		
		-- 1.3.6.1.4.1.42397.1.1.3.1.1.7
		gwnRadioTxMgmtFrames OBJECT-TYPE
			SYNTAX Counter32
			MAX-ACCESS read-only
			STATUS current
			DESCRIPTION
				"Description."
			::= { gwnRadioEntry 7 }

		
		-- 1.3.6.1.4.1.42397.1.1.3.1.1.8
		gwnRadioTxDataFrames OBJECT-TYPE
			SYNTAX Counter32
			MAX-ACCESS read-only
			STATUS current
			DESCRIPTION
				"Description."
			::= { gwnRadioEntry 8 }

		
		-- 1.3.6.1.4.1.42397.1.1.3.1.1.9
		gwnRadioTxDataBytes OBJECT-TYPE
			SYNTAX Counter32
			MAX-ACCESS read-only
			STATUS current
			DESCRIPTION
				"Description."
			::= { gwnRadioEntry 9 }

		
		-- 1.3.6.1.4.1.42397.1.1.3.1.1.10
		gwnRadioTxDrops OBJECT-TYPE
			SYNTAX Counter32
			MAX-ACCESS read-only
			STATUS current
			DESCRIPTION
				"Description."
			::= { gwnRadioEntry 10 }

		
		-- 1.3.6.1.4.1.42397.1.1.3.1.1.11
		gwnRadioRxTotalFrames OBJECT-TYPE
			SYNTAX Counter32
			MAX-ACCESS read-only
			STATUS current
			DESCRIPTION
				"Description."
			::= { gwnRadioEntry 11 }

		
		-- 1.3.6.1.4.1.42397.1.1.3.1.1.12
		gwnRadioRxDataFrames OBJECT-TYPE
			SYNTAX Counter32
			MAX-ACCESS read-only
			STATUS current
			DESCRIPTION
				"Description."
			::= { gwnRadioEntry 12 }

		
		-- 1.3.6.1.4.1.42397.1.1.3.1.1.13
		gwnRadioRxDataBytes OBJECT-TYPE
			SYNTAX Counter32
			MAX-ACCESS read-only
			STATUS current
			DESCRIPTION
				"Description."
			::= { gwnRadioEntry 13 }

		
		-- 1.3.6.1.4.1.42397.1.1.3.1.1.14
		gwnRadioRxMgmtFrames OBJECT-TYPE
			SYNTAX Counter32
			MAX-ACCESS read-only
			STATUS current
			DESCRIPTION
				"Description."
			::= { gwnRadioEntry 14 }

		
		-- 1.3.6.1.4.1.42397.1.1.3.1.1.15
		gwnRadioRxBad OBJECT-TYPE
			SYNTAX Counter32
			MAX-ACCESS read-only
			STATUS current
			DESCRIPTION
				"Description."
			::= { gwnRadioEntry 15 }

		
		-- 1.3.6.1.4.1.42397.1.1.3.2
		gwnWlanTable OBJECT-TYPE
			SYNTAX SEQUENCE OF GwnWlanEntry
			MAX-ACCESS not-accessible
			STATUS current
			DESCRIPTION
				"Description."
			::= { gwnApWireless 2 }

		
		-- 1.3.6.1.4.1.42397.1.1.3.2.1
		gwnWlanEntry OBJECT-TYPE
			SYNTAX GwnWlanEntry
			MAX-ACCESS not-accessible
			STATUS current
			DESCRIPTION
				"Description."
			INDEX { gwnWlanIndex }
			::= { gwnWlanTable 1 }

		
		GwnWlanEntry ::=
			SEQUENCE { 
				gwnWlanIndex
					Integer32,
				gwnWlanESSID
					DisplayString,
				gwnWlanBSSID
					MacAddress,
				gwnWlanTxTotalFrames
					Counter32,
				gwnWlanTxDataFrames
					Counter32,
				gwnWlanTxDataBytes
					Counter32,
				gwnWlanRxTotalFrames
					Counter32,
				gwnWlanRxDataFrames
					Counter32,
				gwnWlanRxDataBytes
					Counter32
			 }

		-- 1.3.6.1.4.1.42397.1.1.3.2.1.1
		gwnWlanIndex OBJECT-TYPE
			SYNTAX Integer32
			MAX-ACCESS read-only
			STATUS current
			DESCRIPTION
				"Description."
			::= { gwnWlanEntry 1 }

		
		-- 1.3.6.1.4.1.42397.1.1.3.2.1.2
		gwnWlanESSID OBJECT-TYPE
			SYNTAX DisplayString
			MAX-ACCESS read-only
			STATUS current
			DESCRIPTION
				"Description."
			::= { gwnWlanEntry 2 }

		
		-- 1.3.6.1.4.1.42397.1.1.3.2.1.3
		gwnWlanBSSID OBJECT-TYPE
			SYNTAX MacAddress
			MAX-ACCESS read-only
			STATUS current
			DESCRIPTION
				"Description."
			::= { gwnWlanEntry 3 }

		
		-- 1.3.6.1.4.1.42397.1.1.3.2.1.4
		gwnWlanTxTotalFrames OBJECT-TYPE
			SYNTAX Counter32
			MAX-ACCESS read-only
			STATUS current
			DESCRIPTION
				"Description."
			::= { gwnWlanEntry 4 }

		
		-- 1.3.6.1.4.1.42397.1.1.3.2.1.5
		gwnWlanTxDataFrames OBJECT-TYPE
			SYNTAX Counter32
			MAX-ACCESS read-only
			STATUS current
			DESCRIPTION
				"Description."
			::= { gwnWlanEntry 5 }

		
		-- 1.3.6.1.4.1.42397.1.1.3.2.1.6
		gwnWlanTxDataBytes OBJECT-TYPE
			SYNTAX Counter32
			MAX-ACCESS read-only
			STATUS current
			DESCRIPTION
				"Description."
			::= { gwnWlanEntry 6 }

		
		-- 1.3.6.1.4.1.42397.1.1.3.2.1.7
		gwnWlanRxTotalFrames OBJECT-TYPE
			SYNTAX Counter32
			MAX-ACCESS read-only
			STATUS current
			DESCRIPTION
				"Description."
			::= { gwnWlanEntry 7 }

		
		-- 1.3.6.1.4.1.42397.1.1.3.2.1.8
		gwnWlanRxDataFrames OBJECT-TYPE
			SYNTAX Counter32
			MAX-ACCESS read-only
			STATUS current
			DESCRIPTION
				"Description."
			::= { gwnWlanEntry 8 }

		
		-- 1.3.6.1.4.1.42397.1.1.3.2.1.9
		gwnWlanRxDataBytes OBJECT-TYPE
			SYNTAX Counter32
			MAX-ACCESS read-only
			STATUS current
			DESCRIPTION
				"Description."
			::= { gwnWlanEntry 9 }

		
		-- 1.3.6.1.4.1.42397.1.1.3.3
		gwnClientTable OBJECT-TYPE
			SYNTAX SEQUENCE OF GwnClientEntry
			MAX-ACCESS not-accessible
			STATUS current
			DESCRIPTION
				"Description."
			::= { gwnApWireless 3 }

		
		-- 1.3.6.1.4.1.42397.1.1.3.3.1
		gwnClientEntry OBJECT-TYPE
			SYNTAX GwnClientEntry
			MAX-ACCESS not-accessible
			STATUS current
			DESCRIPTION
				"Description."
			INDEX { gwnClientMACAddress }
			::= { gwnClientTable 1 }

		
		GwnClientEntry ::=
			SEQUENCE { 
				gwnClientMACAddress
					MacAddress,
				gwnClienttIPAddress
					IpAddress,
				gwnClientWlanMACAddress
					MacAddress,
				gwnClientESSID
					DisplayString,
				gwnClientRSSI
					Integer32,
				gwnClientAssoctime
					TimeTicks,
				gwnClientManufacture
					DisplayString,
				gwnClientHostname
					DisplayString,
				gwnClientOS
					DisplayString,
				gwnClientTxRate
					Integer32,
				gwnClientTxDataFrames
					Counter32,
				gwnClientTxDataBytes
					Counter32,
				gwnClientRxRate
					Integer32,
				gwnClientRxDataFrames
					Counter32,
				gwnClientRxDataBytes
					Counter32,
				gwnClientnode54
					Integer32,
				gwnClientnode55
					Integer32
			 }

		-- 1.3.6.1.4.1.42397.1.1.3.3.1.1
		gwnClientMACAddress OBJECT-TYPE
			SYNTAX MacAddress
			MAX-ACCESS read-only
			STATUS current
			DESCRIPTION
				"Description."
			::= { gwnClientEntry 1 }

		
		-- 1.3.6.1.4.1.42397.1.1.3.3.1.2
		gwnClienttIPAddress OBJECT-TYPE
			SYNTAX IpAddress
			MAX-ACCESS read-only
			STATUS current
			DESCRIPTION
				"Description."
			::= { gwnClientEntry 2 }

		
		-- 1.3.6.1.4.1.42397.1.1.3.3.1.3
		gwnClientWlanMACAddress OBJECT-TYPE
			SYNTAX MacAddress
			MAX-ACCESS read-only
			STATUS current
			DESCRIPTION
				"Description."
			::= { gwnClientEntry 3 }

		
		-- 1.3.6.1.4.1.42397.1.1.3.3.1.4
		gwnClientESSID OBJECT-TYPE
			SYNTAX DisplayString
			MAX-ACCESS read-only
			STATUS current
			DESCRIPTION
				"Description."
			::= { gwnClientEntry 4 }

		
		-- 1.3.6.1.4.1.42397.1.1.3.3.1.5
		gwnClientRSSI OBJECT-TYPE
			SYNTAX Integer32
			MAX-ACCESS read-only
			STATUS current
			DESCRIPTION
				"Description."
			::= { gwnClientEntry 5 }

		
		-- 1.3.6.1.4.1.42397.1.1.3.3.1.6
		gwnClientAssoctime OBJECT-TYPE
			SYNTAX TimeTicks
			MAX-ACCESS read-only
			STATUS current
			DESCRIPTION
				"Description."
			::= { gwnClientEntry 6 }

		
		-- 1.3.6.1.4.1.42397.1.1.3.3.1.7
		gwnClientManufacture OBJECT-TYPE
			SYNTAX DisplayString
			MAX-ACCESS read-only
			STATUS current
			DESCRIPTION
				"Description."
			::= { gwnClientEntry 7 }

		
		-- 1.3.6.1.4.1.42397.1.1.3.3.1.8
		gwnClientHostname OBJECT-TYPE
			SYNTAX DisplayString
			MAX-ACCESS read-only
			STATUS current
			DESCRIPTION
				"Description."
			::= { gwnClientEntry 8 }

		
		-- 1.3.6.1.4.1.42397.1.1.3.3.1.9
		gwnClientOS OBJECT-TYPE
			SYNTAX DisplayString
			MAX-ACCESS read-only
			STATUS current
			DESCRIPTION
				"Description."
			::= { gwnClientEntry 9 }

		
		-- 1.3.6.1.4.1.42397.1.1.3.3.1.10
		gwnClientTxRate OBJECT-TYPE
			SYNTAX Integer32
			MAX-ACCESS read-only
			STATUS current
			DESCRIPTION
				"Description."
			::= { gwnClientEntry 10 }

		
		-- 1.3.6.1.4.1.42397.1.1.3.3.1.11
		gwnClientTxDataFrames OBJECT-TYPE
			SYNTAX Counter32
			MAX-ACCESS read-only
			STATUS current
			DESCRIPTION
				"Description."
			::= { gwnClientEntry 11 }

		
		-- 1.3.6.1.4.1.42397.1.1.3.3.1.12
		gwnClientTxDataBytes OBJECT-TYPE
			SYNTAX Counter32
			MAX-ACCESS read-only
			STATUS current
			DESCRIPTION
				"Description."
			::= { gwnClientEntry 12 }

		
		-- 1.3.6.1.4.1.42397.1.1.3.3.1.13
		gwnClientRxRate OBJECT-TYPE
			SYNTAX Integer32
			MAX-ACCESS read-only
			STATUS current
			DESCRIPTION
				"Description."
			::= { gwnClientEntry 13 }

		
		-- 1.3.6.1.4.1.42397.1.1.3.3.1.14
		gwnClientRxDataFrames OBJECT-TYPE
			SYNTAX Counter32
			MAX-ACCESS read-only
			STATUS current
			DESCRIPTION
				"Description."
			::= { gwnClientEntry 14 }

		
		-- 1.3.6.1.4.1.42397.1.1.3.3.1.15
		gwnClientRxDataBytes OBJECT-TYPE
			SYNTAX Counter32
			MAX-ACCESS read-only
			STATUS current
			DESCRIPTION
				"Description."
			::= { gwnClientEntry 15 }

		
	
	END

--
-- GRANDSTREAM-GWN-MIB.my
--
